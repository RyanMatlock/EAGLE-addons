#usage "<h4>Connector Attributes v0.1 (2014-06-26)</h4>"
       "<br>"
       "<p>This ULP allows you to quickly and efficiently edit groups of "
       "connectors (assumed to start with the reference designator J) in "
       "order to take advantage of connector libraries that label pins on "
       "connectors with \"&gt;<i>i</i>\" where <i>i</i> is the connector "
       "number.  An example of such a library is magzor-connectors.lbr.</p>"
       "<p>This program is provided as-is, without any warranty.</p>"
       "<br>"
       "<p><author>Author: Ryan Matlock (ryan.matlock<ignore>@gmail.com)"
       "</author></p>"

string CONNECTOR_REF_DES = "J"; // connector reference designator


// function borrowed from change-prefix-sch.ulp
// returns index of number in a name (i.e. U2 returns  1, JP2 returns 2)
int get_number_index(string name)
{
    int length = strlen(name) - 1;
    for(int i = length; i >= 0; --i)
    {
        if(!isdigit(name[i]))
        {
            return i < length ? i + 1: -1;
        }
    }
    return 0;
}

int get_prefix_length(string name)
/* assumes prefix is only alpha (i.e. A-Z, a-z) characters, and once it
   encounters something other than that (e.g. a digit, a hyphen, or an
   underscore), it stops incrementing and breaks out of the loop
*/
{
    int length = strlen(name);
    int prefix_length = 0;
    for(int i = 0; i < length; i++)
    {
        if(isalpha(name[i]))
        {
            prefix_length++;
        }
        else
        {
            break;
        }
    }
    return prefix_length;
}
        
    

/* // also borrowed from change-prefix-sch.ulp */
/* string get_prefix(string name) */
/* { */
/*     int index = get_number_index(name); */
/*     if(index < 1) */
/*     { */
/*         return name; */
/*     } */
/*     else */
/*     { */
/*         // I modified this section of the code */
/*         string prefix = ""; */
/*         for(int i = 0; i < index; i++) */
/*         { */
/*             prefix += name[i]; */
/*         } */
/*         return prefix; */
/*     } */
/* } */

string get_prefix(string name)
{
    int prefix_length = get_prefix_length(name);
    string prefix = "";
    for(int i = 0; i < prefix_length; i++)
    {
        prefix += name[i];
    }
    return prefix;
}
    

// use this later
// this won't work yet by a long shot
/* dlgDialog("Connector Attribute Editor") */
/* { */
/*     dlgVBoxLayout */
/*     { */
/*         for(int i = 0; i < NUM_OF_CONNECTORS; i++) */
/*         { */
/*             dlgHBoxLayout */
/*             { */
/*                 dlgLabel(NAME); */
/*                 dlgVBoxLayout */
/*                 { */
/*                     for(int j = 0; i < NUM_OF_PINS; j++) */
/*                     { */
/*                         dlgLabel("Pin %i" % j); */
/*                         dlgStringEdit(pin_j_text); */
/*                     } */
/*                 } */
/*             } */
/*         } */
/*         dlgHBoxLayout */
/*         { */
/*             /\* if you have to go through connector by connector, you may have */
/*                to do */
/*                    dlgPushButton("+&Next") { next(); } */
/*                and */
/*                    dlgPushButton("-&Prev") { prev(); } */
/*                to scroll through the connectors, and on the last one have the */
/*                OK/Cancel thing. *\/ */
/*             dlgPushButton("+&OK") */
/*             { */
/*                 dlgAccept(); */
/*             } */
/*             dlgPushButton("-&Cancel") */
/*             { */
/*                 dlgReject(); */
/*             } */
/*         } */
/*     } */
/* }; */

if(schematic)
{
    schematic(s)
    {
        // note that output does not have a trailing semicolon!!
        output("testing.log")
        s.parts(p)
        {
            //printf(p.name + "\n"); // works!
            if(get_prefix(p.name) == CONNECTOR_REF_DES)
            {
                dlgMessageBox(p.name); // works! -- now for all prefixes
                
            }
        }
    }
    dlgMessageBox("Script ran successfully!");
    exit(0);
}
else
{
    dlgMessageBox("This script can only be executed if the schematic editor is"
                  " open.");
    exit(0);    
}
